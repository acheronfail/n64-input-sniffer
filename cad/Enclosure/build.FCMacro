# Run this macro in FreeCAD. Keep build.py and parameters.json beside it.
import os
p=os.path.dirname(__file__)
exec(compile(open(os.path.join(p,'build.py')).read(),os.path.join(p,'build.py'),'exec'),{'__file__':os.path.join(p,'build.py'),'__name__':'__main__'})
